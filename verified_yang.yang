module dynamic-mmt-probe {

  yang-version 1;

  namespace "urn:ietf:params:xml:ns:yang:dynamic-mmt-probe";
  prefix probe;
  description "Experimental mmt-probe";


  container probe-cfg {
    description "probe tool configuration.";

    leaf input-mode {
      type string;
      default "nobody";
      description "online or offline";
    }

    leaf input-source {
      type string;
      default "nobody";
      description "input-source, interface-name, pcap";
    }

    leaf threads {
      type uint32;
      default 0;
      description "number of threads";
    }
 
    leaf thread-queue {
      type uint32;
      default 1000;
      description "number of packet queued for threads";
    }

    leaf thread-data {
      type uint32;
      default 0;
      description "number of data queued for threads";
    }


    leaf probe-identifier {
      type uint32;
      default 0;
      description "Probe-id";
    }

    leaf license-path {
      type string;
      default "nobody";
      description "path to the license file";
    }

    leaf log-path {
      type string;
      default "nobody";
      description "path to the log file";
    }

    leaf stat-report-period {
      type uint32;
      default 5;
      description "stat reporting period";
    }

    leaf snap-len {
      type uint32;
      default 65535;
      description "snap-len";
    }

  }
 
  container event {
    description "event based report configuration";
    
    leaf number-of-events {
      type uint32;
      default 0;
      description "number of events based reporting";
    }

    list event-based-reporting {
      key event_id;
      leaf event_id {type string;}
      leaf enable {type uint32; default 0;}
      leaf condition {type string;}
      leaf total_attr {type uint32; default 0;}
      leaf nb-output-channel {type uint32; default 0;}

      list attributes {
        key attr_id;
        leaf attr_id {type string;}
        leaf attr {type string;}
      }

      list output-channel {
        key channel_id;
        leaf channel_id {type string;}
        leaf output {type string;}
      }
    }
  }

  container file-output {
    description "Reports are written to file when enabled";
  
    leaf enable {type uint32; default 0;}

    leaf filename {type string; default "dataoutput.csv";}

    leaf location {type string; default "/opt/mmt/probe/result/report/online/";}

    leaf retain_files {type uint32; default 10;}

    leaf sampled_report {type uint32; default 1;}   
  }

}
