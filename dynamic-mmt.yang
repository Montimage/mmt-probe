module dynamic-mmt-probe {

  yang-version 1;

  namespace "urn:ietf:params:xml:ns:yang:dynamic-mmt-probe";
  prefix probe;
  description "Experimental mmt-probe";


  container probe-cfg {
    description "probe tool configuration.";

    leaf input-mode {
      type string;
      default "nobody";
      description "online or offline";
    }

    leaf input-source {
      type string;
      default "nobody";
      description "input-source, interface-name, pcap";
    }

    leaf threads {
      type uint32;
      default 0;
      description "number of threads";
    }
 
    leaf thread-queue {
      type uint32;
      default 1000;
      description "number of packet queued for threads";
    }

    leaf thread-data {
      type uint32;
      default 0;
      description "number of data queued for threads";
    }


    leaf probe-identifier {
      type uint32;
      default 0;
      description "Probe-id";
    }

    leaf license-path {
      type string;
      default "nobody";
      description "path to the license file";
    }

    leaf log-path {
      type string;
      default "nobody";
      description "path to the log file";
    }

    leaf stat-report-period {
      type uint32;
      default 5;
      description "stat reporting period";
    }

    leaf snap-len {
      type uint32;
      default 65535;
      description "snap-len";
    }
    
    leaf report-cache-size{
      type uint64;
      default 300000;
      description "cache size for writing report";
    }

    leaf enable-proto-without-session-stat {
      type uint32;
      default 0;
      description "enable statistics of protocol without session";
    }

    leaf enable-IP-fragmentation-report {
      type uint32;
      default 0;
      description "enable ip frag report";
    }


  }
 
  container session-report {
    description "session based report configuration";
    leaf enable {type uint32; default 0;}
    leaf output_to_file {type uint32; default 0;}
    leaf output_to_redis {type uint32; default 0;}
    leaf output_to_kafka {type uint32; default 0;}
  }

  container security2-report {
    description "security2 report configuration";
    leaf enable {type uint32; default 0;}
    leaf thread_count {type uint32; default 0;}
    leaf rule_mask {type string;}
    leaf excluded_rules {type string;}
    leaf output_to_file {type uint32; default 0;}
    leaf output_to_redis {type uint32; default 0;}
    leaf output_to_kafka {type uint32; default 0;}
  }

  container event {
    description "event based report configuration";
    
    leaf number-of-events {
      type uint32;
      default 0;
      description "number of events based reporting";
    }

    list event-based-reporting {
      key event_id;
      leaf event_id {type string;}
      leaf enable {type uint32; default 0;}
      leaf condition {type string;}
      leaf output_to_file {type uint32; default 0;}
      leaf output_to_redis {type uint32; default 0;}
      leaf output_to_kafka {type uint32; default 0;}
      list attributes {
        key attr_id;
        leaf attr_id {type string;}
        leaf attr {type string;}
      }

    }
  }

  container session-app-report {
    description "Session based application report configuration";

    leaf number-of-app {
      type uint32;
      default 0;
      description "number of app based reporting";
    }

    list app-based-reporting {
      key app_id;
      leaf app_id {type string;}
      leaf enable {type uint32; default 0;}
      leaf condition {type string;}
      list app_attributes {
        key app_attr_id;
        leaf app_attr_id {type string;}
        leaf app_attr {type string;}
        leaf app_attr_handler {type string;}
      }
    }
  }


  container file-output {
    description "Reports are written to file when enabled";
  
    leaf enable {type uint32; default 0;}

    leaf filename {type string; default "dataoutput.csv";}

    leaf location {type string; default "/opt/mmt/probe/result/report/online/";}

    leaf retain_files {type uint32; default 10;}

    leaf sampled_report {type uint32; default 1;} 

    leaf file_output_period {type uint32; default 5;}  
  }

  container redis-output {
    description "Reports are written to redis when enabled";

    leaf enable {type uint32; default 0;}

    leaf hostname {type string; default "localhost";}

    leaf port {type uint32; default 6379;}
  }

  container kafka-output {
    description "Reports are written to kafka when enabled";

    leaf enable {type uint32; default 0;}

    leaf hostname {type string; default "localhost";}

    leaf port {type uint32; default 9092;}
  }

}
